module ieee802-dot1q-lldp-aa-tlv {
  yang-version "1.1";
  namespace urn:ieee:std:802.1Q:yang:ieee802-dot1q-lldp-aa-tlv;
  prefix lldp-aa-tlv;
  import ieee802-dot1ab-lldp {
    prefix lldp;
  }
  organization
    "Institute of Electrical and Electronics Engineers";
  contact
    "WG-URL: http://ieee802.org/1/
    WG-EMail: stds-802-1-l@ieee.org
    Contact: IEEE 802.1 Working Group Chair
    Postal: C/O IEEE 802.1 Working Group
    IEEE Standards Association
         445 Hoes Lane
         Piscataway, NJ 08854
         USA
    
    E-mail: stds-802-1-chairs@ieee.org";
  description
    "IEEE Std 802.1Qcj extension tlvs for LLDP
    
    Copyright (C) IEEE (2022).
    
    This version of this YANG module is part of IEEE Std 802.1Q; see the
    standard itself for full legal notices.";
  revision 2022-07-28 {
    description
      "LLDP extension tlv for Auto Attach. Published as part of IEEE Std
      802.1Qcj-2022.";
    reference
      "Annex D of IEEE Std 802.1Qcj-2022";
  }
  grouping aa-system-tlv {
    description
      "Auto Attach System TLV";
    reference
      "D.2.17 of IEEE Std 802.1Q-2022";
    leaf aa-system-tlv-info-string {
      type binary {
        length "0..20";
      }
      config false;
      description
        "Opaque string containing Aa System TLV information string. As the
        elements within the string are not individually manipulated by
        management (they are of concern only to the state machines), the
        sub-structure of the string is not visible as separate objects
        within the local database.";
      reference
        "D.2.17 of IEEE Std 802.1Q-2022";
    }
  }
  grouping aa-assign-tlv {
    description
      "Auto Attach System TLV";
    reference
      "D.2.18 of IEEE Std 802.1Q-2022";
    leaf aa-assign-info-string {
      type binary {
        length "0..510";
      }
      config false;
      description
        "Opaque string containing Auto Attach Assignment TLV information.
        Up to 101 VID/I-SID assignments are supported. As the elements
        within the string are not individually manipulated by management
        (they are of concern only to the state machines), the sub-structure
        of the string is not visible as separate objects within the local
        database.";
      reference
        "D.2.18 and D.2.18.8 of IEEE Std 802.1Q-2022";
    }
  }
  augment "/lldp:lldp/lldp:port" {
    description
      "Augments port with the evb extension tlv";
    leaf tlvs-tx-org-aa-system-enable {
      type bits {
        bit aaSystem {
          position 0;
          description
            "D.2.17 of IEEE Std 802.1Q-2022";
        }
        bit aaAssign {
          position 1;
          description
            "D.2.18 of IEEE Std 802.1Q-2022";
        }
      }
      description
        "Bitmap that includes the evbSet of tlvs from Table D.1 of
        802.1Q-2022";
      reference
        "D.1 of IEEE Std 802.1Q-2022";
    }
    container aa-system-tlv-extension {
      description
        "The Auto Attach System TLV";
      uses aa-system-tlv;
    }
    container aa-assign-tlv-extension {
      description
        "The Auto Attach Assignment TLV";
      uses aa-assign-tlv;
    }
  }
  augment "/lldp:lldp/lldp:port/lldp:remote-systems-data" {
    description
      "Augments port remote-systems-data with received aa extension tlvs";
    container aa-system-tlv-extension {
      description
        "Holds a received Auto Attach System TLV";
      uses aa-system-tlv;
    }
    container aa-assign-tlv-extension {
      description
        "Holds a received Auto Attach Assignment TLV";
      uses aa-assign-tlv;
    }
  }
}
